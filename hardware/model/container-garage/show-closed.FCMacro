"""Display the closed pose without saving or changing other documents."""
from pathlib import Path
import sys
sys.path.insert(0, str(Path(__file__).resolve().parents[3] / 'scripts'))
import container_garage
container_garage.show_saved_pose('closed')
